FME workspace converte_nomes_3cgeo.fmw

Parameters:
- SourceDataset_POSTGIS = operacao_fogo_4674_edgvtopo14multi   # Banco de dados multiescala
- HOST_POSTGIS = 10.25.163.12   # Host BD Multiescala
- PORT_POSTGIS = 5434   # Port BD Multiescala
- USER_NAME_POSTGIS = postgres   # Username BD Multiescala
- PASSWORD_POSTGIS =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   # Password BD Multiescala
- FEATURE_TYPES = edgv.aux_moldura_50k_a edgv.aux_moldura_area_continua_50k_a edgv.aux_observacao_50k_a edgv.aux_observacao_50k_l edgv.aux_observacao_50k_p edgv.aux_reambulacao_50k_a edgv.aux_reambulacao_50k_l edgv.aux_reambulacao_50k_p edgv.aux_revisao_50k_a edgv.aux_revisao_50k_l edgv.aux_revisao_50k_p edgv.centroide_area_edificada_50k_p edgv.centroide_area_sem_dados_50k_p edgv.centroide_elemento_hidrografico_50k_p edgv.centroide_ilha_50k_p edgv.centroide_limite_especial_50k_p edgv.centroide_massa_dagua_50k_p edgv.centroide_vegetacao_50k_p edgv.cobter_area_edificada_50k_a edgv.cobter_massa_dagua_50k_a edgv.cobter_vegetacao_50k_a edgv.constr_area_uso_especifico_50k_a edgv.constr_deposito_50k_a edgv.constr_deposito_50k_p edgv.constr_edificacao_50k_a edgv.constr_edificacao_50k_p edgv.constr_extracao_mineral_50k_a edgv.constr_extracao_mineral_50k_p edgv.constr_ocupacao_solo_50k_a edgv.constr_ocupacao_solo_50k_l edgv.constr_ocupacao_solo_50k_p edgv.delimitador_area_edificada_50k_l edgv.delimitador_area_sem_dados_50k_l edgv.delimitador_elemento_hidrografico_50k_l edgv.delimitador_limite_especial_50k_l edgv.delimitador_massa_dagua_50k_l edgv.delimitador_vegetacao_50k_l edgv.edicao_borda_elemento_hidrografico_50k_l edgv.edicao_grid_edicao_50k_l edgv.edicao_grid_numerico_50k_p edgv.edicao_identificador_trecho_rod_50k_p edgv.edicao_limite_especial_50k_l edgv.edicao_ponto_mudanca_50k_p edgv.edicao_simb_area_50k_p edgv.edicao_simb_cota_mestra_50k_l edgv.edicao_simb_direcao_corrente_50k_p edgv.edicao_simb_torre_energia_50k_p edgv.edicao_simb_vegetacao_50k_p edgv.edicao_texto_generico_50k_l edgv.edicao_texto_generico_50k_p edgv.elemnat_curva_nivel_50k_l edgv.elemnat_elemento_fisiografico_50k_a edgv.elemnat_elemento_fisiografico_50k_l edgv.elemnat_elemento_fisiografico_50k_p edgv.elemnat_elemento_hidrografico_50k_a edgv.elemnat_elemento_hidrografico_50k_l edgv.elemnat_elemento_hidrografico_50k_p edgv.elemnat_ilha_50k_a edgv.elemnat_ilha_50k_p edgv.elemnat_ponto_cotado_50k_p edgv.elemnat_sumidouro_vertedouro_50k_p edgv.elemnat_terreno_sujeito_inundacao_50k_a edgv.elemnat_toponimo_fisiografico_natural_50k_l edgv.elemnat_toponimo_fisiografico_natural_50k_p edgv.elemnat_trecho_drenagem_50k_l edgv.infra_alteracao_fisiografica_antropica_50k_l edgv.infra_barragem_50k_a edgv.infra_barragem_50k_l edgv.infra_elemento_energia_50k_a edgv.infra_elemento_energia_50k_l edgv.infra_elemento_energia_50k_p edgv.infra_elemento_infraestrutura_50k_a edgv.infra_elemento_infraestrutura_50k_l edgv.infra_elemento_infraestrutura_50k_p edgv.infra_elemento_viario_50k_l edgv.infra_ferrovia_50k_l edgv.infra_mobilidade_urbana_50k_l edgv.infra_obstaculo_vertical_50k_p edgv.infra_pista_pouso_50k_a edgv.infra_pista_pouso_50k_l edgv.infra_pista_pouso_50k_p edgv.infra_travessia_hidroviaria_50k_l edgv.infra_travessia_hidroviaria_50k_p edgv.infra_trecho_duto_50k_l edgv.infra_trecho_hidroviario_50k_l edgv.infra_vala_50k_l edgv.infra_via_deslocamento_50k_l edgv.llp_area_sem_dados_50k_a edgv.llp_limite_especial_50k_a edgv.llp_limite_legal_50k_l edgv.llp_localidade_50k_p edgv.llp_pais_50k_a edgv.llp_ponto_controle_50k_p edgv.llp_unidade_federacao_50k_a
- HOST_POSTGIS_2 = 10.25.163.12   # Host Municípios
- PORT_POSTGIS_2 = 5432   # Port Municípios
- USER_NAME_POSTGIS_2 = postgres   # Username Municípios
- PASSWORD_POSTGIS_2 =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   # Password Municípios
- SourceDataset_POSTGIS_3 = acervo   # Banco de dados Municípios
- POSTGIS_IN_WHERE_CLAUSE_POSTGIS_3 =   # "" Filtro muncípios
- FEATURE_TYPES_2 = insumos.municipio
- DestDataset_POSTGIS = operacao_fogo_4674_nomes_geograficos   # Banco de dados Nomes Geográficos
- HOST_POSTGIS_3 = 10.25.163.12   # Host Nomes Geográficos
- USER_NAME_POSTGIS_3 = user_nomes_geograficos   # Username Nomes Geográficos
- PORT_POSTGIS_3 = 5434   # Port Nomes Geográficos
- PASSWORD_POSTGIS_3 =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   # Password Nomes Geográficos

Readers:
- POSTGIS_1: POSTGIS from $(SourceDataset_POSTGIS)
- POSTGIS_2: POSTGIS from $(SourceDataset_POSTGIS_3)

Writers:
- POSTGIS_3: POSTGIS to $(DestDataset_POSTGIS)

Note: Camada de municipio, pode modificar
municipio (reader POSTGIS_2)
    attributes: id serial,PrimaryKey, nome varchar(255), codigo varchar(255), sigla_uf varchar(255), codigo_uf varchar(255)
    -> AttributeCreator
Note: Aqui acerta os atributos para ser estado e municipio
AttributeCreator
    ATTR_TABLE:
      SET_TO estado (varchar(255)) = @Value(sigla_uf)
      SET_TO municipio (varchar(255)) = @Value(nome)
    -> StringCaseChanger
StringCaseChanger
    ATTRCHOICE = Selected Attributes
    ATTRLIST = municipio
    CHANGE_TYPE = Full Title Case
    -> StringCaseChanger_2
StringCaseChanger_2
    ATTRCHOICE = Selected Attributes
    ATTRLIST = estado
    CHANGE_TYPE = UPPERCASE
    -> Reprojector
Reprojector
    DEST = EPSG:4674
    INTERPOLATION_TYPE_NAME = Nearest Neighbor
    RASTER_CELL_SIZE = Preserve Cells
    RASTER_TOLERANCE = 0.0
    REPROJECTED -> Clipper [CLIPPER]
aux_insumo_externo_100k_a (reader POSTGIS_1)
    attributes: id uuid, nome varchar(255), fonte varchar(255), observacao varchar(255), administracao_code int2, administracao_value varchar(255), altitude float4, altitude_geometrica varchar(255), altitude_ortometrica varchar(255), ancora_horizontal_code int2, ancora_horizontal_value varchar(255), ancora_vertical_code int2, ancora_vertical_value varchar(255), assentamento_precario_code int2, assentamento_precario_value varchar(255), bitola_code int2, bitola_value varchar(255), canteiro_divisorio_code int2, canteiro_divisorio_value varchar(255), cod_ponto varchar(255), concessionaria varchar(255), cor varchar(255), corrigido_code int2, corrigido_value varchar(255), cota int4, cota_comprovada_code int2, cota_comprovada_value varchar(255), cota_mais_alta_code int2, cota_mais_alta_value varchar(255), densamente_edificada_code int2,
      densamente_edificada_value varchar(255), dentro_de_massa_dagua_code int2, dentro_de_massa_dagua_value varchar(255), depressao_code int2, depressao_value varchar(255), descricao varchar(255), desloc float4, direcao_fixada_code int2, direcao_fixada_value varchar(255), eletrificada_code int2, eletrificada_value varchar(255), em_arruamento_code int2, em_arruamento_value varchar(255), espacamento float4, estilo_fonte varchar(255), exibir_lado_simbologia_code int2, exibir_lado_simbologia_value varchar(255), exibir_linha_rotulo_code int2, exibir_linha_rotulo_value varchar(255), exibir_ponta_simbologia_code int2, exibir_ponta_simbologia_value varchar(255), exibir_rotulo_aproximado_code int2, exibir_rotulo_aproximado_value varchar(255), finalidade_code int2, finalidade_value varchar(255), forma_extracao_code int2, forma_extracao_value varchar(255), geometria_aproximada_code int2, geometria_aproximada_value varchar(255), indice_code int2,
      indice_value varchar(255), inom varchar(255), jurisdicao_code int2, jurisdicao_value varchar(255), justificativa varchar(255), justificativa_txt_code int2, justificativa_txt_value varchar(255), label_x float4, label_y float4, largura_simbologia float4, latitude varchar(255), longitude varchar(255), material_construcao_code int2, material_construcao_value varchar(255), mi varchar(255), modal_uso_code int2, modal_uso_value varchar(255), nr_faixas varchar(255), nr_linhas_code int2, nr_linhas_value varchar(255), nr_pistas varchar(255), ordem_simbologia int4, orgao_responsavel varchar(255), populacao int4, posicao_pista_code int2, posicao_pista_value varchar(255), posicao_relativa_code int2, posicao_relativa_value varchar(255), posicao_rotulo_code int2, posicao_rotulo_value varchar(255),
      referencial_altim_code int2, referencial_altim_value varchar(255), referencial_grav_code int2, referencial_grav_value varchar(255), regime_code int2, regime_value varchar(255), revestimento_code int2, revestimento_value varchar(255), sigla varchar(255), simb_rot float4, sistema_geodesico_code int2, sistema_geodesico_value varchar(255), situacao_em_poligono_code int2, situacao_em_poligono_value varchar(255), situacao_fisica_code int2, situacao_fisica_value varchar(255), situacao_marco_code int2, situacao_marco_value varchar(255), sobreposto_code int2, sobreposto_transportes_code int2, sobreposto_transportes_value varchar(255), sobreposto_value varchar(255), subfase_id int4, sujeito_inundacao_code int2, sujeito_inundacao_value varchar(255), suprimir_bandeira_code int2, suprimir_bandeira_value varchar(255), suprimir_simbologia_code int2, suprimir_simbologia_value varchar(255), tamanho_txt float4,
      texto_edicao varchar(255), tipo_code int2, tipo_exposicao_code int2, tipo_exposicao_value varchar(255), tipo_produto_code int2, tipo_produto_value varchar(255), tipo_ref_code int2, tipo_ref_value varchar(255), tipo_value varchar(255), trafego_code int2, trafego_value varchar(255), uso_pista_code int2, uso_pista_value varchar(255), visivel_code int2, visivel_value varchar(255)
    -> Deaggregator_2
Deaggregator_2
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> AttributeKeeper_3
AttributeKeeper_3
    CREATE_BULK_MODE_FEATURES = NO
    KEEP_ATTRS = nome,fme_feature_type,tipo_value,sigla
    -> Tester_4
Tester_4
    BOOL_OP = OR
    TEST_CLAUSE = TEST sigla ATTRIBUTE_HAS_A_VALUE ""
    TEST_MODE = TEST
    PASSED -> AttributeSplitter
    FAILED -> Tester_3
AttributeSplitter
    ATTR_NAME = sigla
    DELIMITER = ;
    DROP_EMPTY_PARTS = Yes
    LIST_NAME = _list
    TRIM_OPTION = Both
    -> ListExploder
ListExploder
    ATTR_ACCUM_MODE = Merge List Attributes
    ATTR_CONFLICT_RES = Use List Attribute Values
    INDEX_ATTR = _element_index
    LIST_ATTR = _list{}
    ELEMENTS -> AttributeCreator_4
AttributeCreator_4
    ATTR_TABLE = SET_TO nome (varchar(200)) = @Value(_list)
    -> Clipper [CANDIDATE]
Tester_3
    BOOL_OP = OR
    TEST_CLAUSE = CASE_INSENSITIVE_TEST nome ATTRIBUTE_HAS_A_VALUE ""
    TEST_MODE = CASE_INSENSITIVE_TEST
    PASSED -> Clipper [CANDIDATE]
Clipper
    ADD_NODATA = YES
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Deaggregator
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> GeometryFilter
GeometryFilter
    FILTER_MODE = SIMPLE
    FILTER_MULTI = FILTER_TYPES]"Line Area Point"]FME_CONTROLLER_QUERY_FILE]]FME_CONTROLLER_CHOICE]Simple
    Point -> CoordinateExtractor
    Curve -> VertexCounter
    Area -> CenterPointReplacer
CenterPointReplacer
    POINTTYPE = INSIDE
    POINT -> CoordinateExtractor
VertexCounter
    CNT_ATTR = _vertexcount
    -> CoordinateExtractor_2
CoordinateExtractor_2
    IND = @floor(@Value(_vertexcount)/2,0)
    MODE = Specify Coordinate
    X_ATTR = x
    Y_ATTR = y
    -> VertexCreator
VertexCreator
    MEASURE_TYPE = Continuous
    MODE_NAME = Replace with Point
    XVAL = @Value(x)
    YVAL = @Value(y)
    -> CoordinateExtractor
CoordinateExtractor
    IND = 0
    MODE = Specify Coordinate
    X_ATTR = long
    Y_ATTR = lat
    -> DuplicateFilter_2
DuplicateFilter_2
    INPUT_ORDERED_CHOICE = No
    KEYATTR = estado fme_feature_type municipio nome tipo_value
    UNIQUE -> AttributeCreator_2
AttributeCreator_2
    ATTR_TABLE = SET_TO tipo (varchar(255)) = @Value(tipo_value)
    -> UniqueIdentifierGenerator
UniqueIdentifierGenerator
    UUID_ATTR = id
    UUID_FORMAT = UUID_ONLY
    -> nomes_geograficos (writer POSTGIS_3)
nomes_geograficos (writer POSTGIS_3)
    attributes: id uuid, nome varchar(255), municipio varchar(255), estado varchar(255), tipo varchar(255),BTree
